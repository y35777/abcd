--2.5G GPRS 话单格式 
--包含中国移动的计费网关规范V1.3.0


CDR2G 
DEFINITIONS IMPLICIT TAGS ::=

BEGIN

CallEventRecord	::= CHOICE 
{
	sgsnPDPRecord		[0] SGSNPDPRecord,
	ggsnPDPRecord		[1] GGSNPDPRecord,
	sgsnMMRecord		[2] SGSNMMRecord,
	sgsnSMORecord		[3] SGSNSMORecord,
	sgsnSMTRecord		[4] SGSNSMTRecord
}

GGSNPDPRecord 	::= SET
{
	recordType			[0]  CallEventRecordType,
	networkInitiation		[1]  NetworkInitiatedPDPContext OPTIONAL,
	anonymousAccessIndicator	[2]  BOOLEAN OPTIONAL,
	servedIMSI			[3]  IMSI,
	ggsnAddress			[4]  GSNAddress,
	chargingID			[5]  ChargingID,
	sgsnAddress			[6]  SEQUENCE OF GSNAddress,
	accessPointNameNI		[7]  AccessPointNameNI,
	pdpType			[8]  PDPType,
	servedPDPAddress		[9]  PDPAddress,
	remotePDPAddress		[10] SEQUENCE OF PDPAddress OPTIONAL,
	dynamicAddressFlag		[11] DynamicAddressFlag OPTIONAL,
	listOfTrafficVolumes		[12] SEQUENCE OF ChangeOfCharCondition,
	recordOpeningTime		[13] TimeStamp,
	duration			[14] CallDuration,
	causeForRecClosing		[15] CauseForRecClosing,
	recordSequenceNumber            [17] RECORDSequenceNumber OPTIONAL,
	nodeID				[18] NodeID OPTIONAL,
	recordExtensions		[19] ManagementExtensions OPTIONAL,
	apnSelectionMode		[21] APNSelectionMode OPTIONAL,
	servedMSISDN 			[29] MSISDN OPTIONAL,
	consolidationResult         [30] ConsolidationResult
}

SGSNPDPRecord 	::= SET
{
	recordType			[0]  CallEventRecordType,
	networkInitiation		[1]  NetworkInitiatedPDPContext OPTIONAL,
	anonymousAccessIndicator	[2]  BOOLEAN OPTIONAL,
	servedIMSI			[3]  IMSI ,
	servedIMEI			[4]  IMEI OPTIONAL,
	sgsnAddress                     [5]  SEQUENCE OF GSNAddress,
	msNetworkCapability		[6]  MSNetworkCapability OPTIONAL,
	routingArea			[7]  RoutingAreaCode OPTIONAL,
	locationAreaCode		[8]  LocationAreaCode OPTIONAL,
	cellIdentity			[9]  CellId OPTIONAL,
	chargingID			[10] ChargingID,
	ggsnAddressUsed		[11] GSNAddress,
	accessPointNameNI		[12] AccessPointNameNI,
	pdpType			[13] PDPType,
	servedPDPAddress		[14] PDPAddress,
	listOfTrafficVolumes		[15] SEQUENCE OF ChangeOfCharCondition,
	recordOpeningTime		[16] TimeStamp,
	duration			[17] CallDuration,
	sgsnChange			[18] SGSNChange OPTIONAL,
	causeForRecClosing		[19] CauseForRecClosing,
	recordSequenceNumber        [21] SEQUENCE OF RECORDSequenceNumber OPTIONAL,
	nodeID				[22] NodeID OPTIONAL,
	recordExtensions		[23] ManagementExtensions OPTIONAL,
	apnSelectionMode		[25] APNSelectionMode OPTIONAL,
	accessPointNameOI		[26] AccessPointNameOI,
	servedMSISDN 			[29] MSISDN OPTIONAL,
	consolidationResult         [30] ConsolidationResult
}

SGSNMMRecord	::= SET
{
	recordType			[0]  CallEventRecordType,
	servedIMSI			[1]  IMSI ,
	servedIMEI			[2]  IMEI OPTIONAL,
	sgsnAddress			[3]  GSNAddress,
	msNetworkCapability		[4]  MSNetworkCapability OPTIONAL,
	routingArea			[5]  RoutingAreaCode OPTIONAL,	
	locationAreaCode		[6]  LocationAreaCode OPTIONAL,
	cellIdentity			[7]  CellId OPTIONAL,
	changeLocation		[8]  SEQUENCE OF ChangeLocation OPTIONAL,
	recordOpeningTime		[9]  TimeStamp,
	duration			[10] CallDuration OPTIONAL, 
	sgsnChange			[11] SGSNChange OPTIONAL,
	causeForRecClosing		[12] CauseForRecClosing,
	diagnostics			[13] Diagnostics OPTIONAL,
	recordSequenceNumber		[14] INTEGER OPTIONAL,
	nodeID				[15] NodeID OPTIONAL,
	recordExtensions		[16] ManagementExtensions OPTIONAL,
	localSequenceNumber		[17] LocalSequenceNumber OPTIONAL
}

SGSNSMORecord	::= SET
{
	recordType			[0]  CallEventRecordType,
	servedIMSI			[1]  IMSI,
	servedIMEI			[2]  IMEI OPTIONAL,
	servedMSISDN			[3]  MSISDN OPTIONAL,
	msNetworkCapability		[4]  MSNetworkCapability,
	serviceCentre			[5]  AddressString,
	recordingEntity		[6]  RecordingEntity,
	locationArea			[7]  LocationAreaCode OPTIONAL,
	routingArea			[8]  RoutingAreaCode OPTIONAL,
	cellIdentity			[9]  CellId OPTIONAL,
	messageReference		[10] MessageReference,
	originationTime		[11] TimeStamp,
	smsResult			[12] SMSResult OPTIONAL,
	recordExtensions		[13] ManagementExtensions OPTIONAL, 
	nodeID				[14] NodeID OPTIONAL,
	localSequenceNumber		[15] LocalSequenceNumber OPTIONAL
}

SGSNSMTRecord	::= SET
{
	recordType			[0]  CallEventRecordType,
	servedIMSI			[1]  IMSI,
	servedIMEI			[2]  IMEI OPTIONAL,
	servedMSISDN			[3]  MSISDN OPTIONAL,
	msNetworkCapability		[4]  MSNetworkCapability,
	serviceCentre			[5]  AddressString,
	recordingEntity		[6]  RecordingEntity,
	locationArea			[7]  LocationAreaCode OPTIONAL,
	routingArea			[8]  RoutingAreaCode OPTIONAL,
	cellIdentity			[9]  CellId OPTIONAL,
	originationTime		[10] TimeStamp,
	smsResult			[11] SMSResult OPTIONAL,
	recordExtensions		[12] ManagementExtensions OPTIONAL,
	nodeID				[13] NodeID OPTIONAL,
	localSequenceNumber		[14] LocalSequenceNumber OPTIONAL
}

--------------------------------------------------------------------------------
--
--  COMMON DATA TYPES
--
--------------------------------------------------------------------------------
AccessPointNameNI ::= IA5String (SIZE(1..63))
--
-- Network Identifier part of APN in "dot" representation
-- see GSM 03.03
--
-- The syntax of the APN follows the Name Syntax defined in IETF RFC
-- 2181 and RFC 1035. The APN consists of one or more labels. Each label is
-- coded as one octet length field followed by that number of octets coded as 8
-- bit ASCII characters. Following RFC 1035 the labels consist only of the
-- alphabetic characters (A-Z and a -z), digits (0-9) and the dash (-). The APN
-- is not terminated by a length byte of zero.
-- <label> ::= <letter> [ [ <ldh-str> ] <let-dig> ]
-- <ldh-str> ::= <let-dig-hyp> | <let-dig-hyp> <ldh-str>
-- <let-dig-hyp> ::= <let-dig> | "-"
-- <let-dig> ::= <letter> | <digit>
-- <letter> ::= any one of the 52 alphabetic characters A through Z in
--                 upper case and a through z in lower case
-- <digit> ::= any one of the ten digits 0 through 9

AccessPointNameOI ::= IA5String (SIZE(1..37))
--
-- Operator Identifier part of APN in "dot" representation
-- see GSM 03.03
--
-- The syntax of the APN follows the Name Syntax defined in IETF RFC
-- 2181 and RFC 1035. The APN consists of one or more labels. Each label is
-- coded as one octet length field followed by that number of octets coded as 8
-- bit ASCII characters. Following RFC 1035 the labels consist only of the
-- alphabetic characters (A-Z and a -z), digits (0-9) and the dash (-). The APN
-- is not terminated by a length byte of zero.
-- <label> ::= <letter> [ [ <ldh-str> ] <let-dig> ]
-- <ldh-str> ::= <let-dig-hyp> | <let-dig-hyp> <ldh-str>
-- <let-dig-hyp> ::= <let-dig> | "-"
-- <let-dig> ::= <letter> | <digit>
-- <letter> ::= any one of the 52 alphabetic characters A through Z in
--                 upper case and a through z in lower case
-- <digit> ::= any one of the ten digits 0 through 9

APNSelectionMode ::= ENUMERATED
{
	--
	-- See Information Elements TS GSM 09.60
	--
	mSorNetworkProvidedSubscriptionVerified		(0),
	mSProvidedSubscriptionNotVerified		(1),
	networkProvidedSubscriptionNotVerified		(2)
}

CauseForRecClosing	::= INTEGER
{
	--
	-- in GGSN the value sGSNChange should be used for partial record
	-- generation due to SGSN Address List Overflow
	--
	-- cause codes 0 to 15 are defined in GSM12.05 as 'CauseForTerm' (cause for termination)
	--
	normalRelease			(0),
	abnormalRelease			(4),
	volumeLimit			(16),
	timeLimit			(17),
	sGSNChange			(18),
	maxChangeCond			(19),
	managementIntervention		(20)
}

ChangeCondition	::= ENUMERATED
{
	qoSChange			(0),
	tariffTime			(1),
	recordClosure			(2)
}

ChangeOfCharCondition	::= SEQUENCE
	--
	-- used in PDP context record only
	--
{
	qosRequested			[1] QoSInformation OPTIONAL,
	qosNegotiated			[2] QoSInformation OPTIONAL,
	dataVolumeGPRSUplink		[3] DataVolumeGPRS,
	dataVolumeGPRSDownlink		[4] DataVolumeGPRS,
	changeCondition			[5] ChangeCondition,
	changeTime			[6] TimeStamp
}

ChangeLocation	::= SEQUENCE
	--
	-- used in SGSNMMRecord only
	--
{
	locationAreaCode		[0] LocationAreaCode,
	routingAreaCode			[1] RoutingAreaCode,
	cellId				[2] CellId OPTIONAL,
	changeTime			[3] TimeStamp
}

ChargingID ::= INTEGER (0..4294967295)
--
-- generated in GGSN, part of PDP context, see TS GSM 03.60
-- 0..4294967295 is equivalent to 0..2**32-1

DataVolumeGPRS	::= INTEGER
	--
	-- The volume of uncompressed data transferred in octets.
	--

DynamicAddressFlag	::= BOOLEAN

ETSIAddress	::= AddressString
	--
	--first octet for nature of address, and numbering plan indicator (3 for X.121)
	--other octets TBCD
	-- See TS GSM 09.02
	--

GSNAddress	::= IPAddress

IPAddress	::= CHOICE
{
	iPBinaryAddress	 IPBinaryAddress,
	iPTextRepresentedAddress	 IPTextRepresentedAddress
}
IPBinaryAddress	::= CHOICE
{
	iPBinV4Address			[0] OCTET STRING (SIZE(4)),
	iPBinV6Address			[1] OCTET STRING (SIZE(16))
}
IPTextRepresentedAddress	::= CHOICE
{	--
	-- IP address in the familiar "dot" notation
	--
	iPTextV4Address			[2] IA5String (SIZE(7..15)),
	iPTextV6Address			[3] IA5String (SIZE(15..45))
}

LocalSequenceNumber  ::= INTEGER (0..4294967295)
	--
	-- Sequence number of the record in this node
	-- 0.. 4294967295 is equivalent to 0..2**32-1, unsigned integer in four octets

MSNetworkCapability	::= OCTET STRING (SIZE(1))

NetworkInitiatedPDPContext	::= BOOLEAN
	--
	-- Set to true if PDP context was initiated from network side
	--
	
NodeID	::= IA5String (SIZE(1..20))

PDPAddress	::= CHOICE
{
	iPAddress			[0] IPAddress,
	eTSIAddress			[1] ETSIAddress
}

PDPType		::= OCTET STRING (SIZE(2))
	--
	--OCTET 1: PDP Type Organization
	--OCTET 2: PDP Type Number
	-- See TS GSM 09.60
	--

QoSDelay		::= ENUMERATED
{
	--
	-- See Quality of service TS GSM 04.08
	--
	delayClass1			(1),
	delayClass2			(2),
	delayClass3			(3),
	delayClass4			(4)
}

QoSInformation	::=SEQUENCE
{
	reliability			[0] QoSReliability,
	delay				[1] QoSDelay,
	precedence			[2] QoSPrecedence,
	peakThroughput			[3] QoSPeakThroughput,
	meanThroughput			[4] QoSMeanThroughput
}

QoSMeanThroughput	::= ENUMERATED
{
	--
	-- See Quality of service TS GSM 04.08
	--
	bestEffort			(0),
	mean100octetPh			(1),
	mean200octetPh			(2),
	mean500octetPh			(3),
	mean1000octetPh			(4),
	mean2000octetPh			(5),
	mean5000octetPh			(6),
	mean10000octetPh		(7),
	mean20000octetPh		(8),
	mean50000octetPh		(9),
	mean100000octetPh		(10),
	mean200000octetPh		(11),
	mean500000octetPh		(12),
	mean1000000octetPh		(13),
	mean2000000octetPh		(14),
	mean5000000octetPh		(15),
	mean10000000octetPh		(16),
	mean20000000octetPh		(17),
	mean50000000octetPh		(18)
}

QoSPeakThroughput	::= ENUMERATED
{
	--
	-- See Quality of service TS GSM 04.08
	--
	unspecified			(0),
	upTo100OctetPs			(1),
	upTo200OctetPs			(2),
	upTo400OctetPs			(3),
	upTo800OctetPs			(4),
	upTo1600OctetPs			(5),
	upTo3200OctetPs			(6),
	upTo6400OctetPs			(7),
	upTo12800OctetPs		(8),
	upTo25600OctetPs		(9)
}

QoSPrecedence	::= ENUMERATED
{
	--
	-- See Quality of service TS GSM 04.08
	--
	unspecified			(0),
	highPriority			(1),
	normalPriority			(2),
	lowPriority			(3)
}

QoSReliability	::= ENUMERATED
{
	--
	-- See Quality of service TS GSM 04.08
	--
	unspecifiedReliability		(0),
	acknowledgedGTP			(1),
	unackGTPAcknowLLC		(2),
	unackGTPLLCAcknowRLC		(3),
	unackGTPLLCRLC			(4),
	unacknowUnprotectedData		(5)
}

RoutingAreaCode	::= OCTET STRING (SIZE(1))
	--
	-- See TS GSM 04.08	--
	--	

SGSNChange	::= BOOLEAN
	--
	-- present if first record after inter SGSN routing area update
	-- in new SGSN
	--

--Changes (enhancements) in GSM1205-DataTypes:

CallEventRecordType 	::= INTEGER 
{ 
	sgsnPDPRecord			(18),
	ggsnPDPRecord			(19),
	sgsnMMRecord			(20),
	sgsnSMORecord			(21),
	sgsnSMTRecord			(22)
}

-- From other Protocol:
-- 1. GSM 12.05 V7.0.0 (1999-04)
-- 2. 3GPP TS 29.002 V3.7.0 (2000-12)  17.7.8 Common data types

CellId	::= OCTET STRING (SIZE(2))
	--
	-- Coded according to TS GSM 04.08	
	--

Diagnostics						::= CHOICE
{
	gsm0408Cause			[0] INTEGER,
	-- See TS GSM 04.08	
	gsm0902MapErrorValue		[1] INTEGER,
	-- Note: The value to be stored here corresponds to
	-- the local values defined in the MAP-Errors and 
	-- MAP-DialogueInformation modules, for full details
	-- see TS GSM 09.02.
	ccittQ767Cause			[2] INTEGER,
	-- See CCITT Q.767	
	networkSpecificCause		[3] ManagementExtension,
	-- To be defined by network operator	
	manufacturerSpecificCause	[4] ManagementExtension
	-- To be defined by manufacturer	
}

CallDuration 			::= INTEGER
	--
	-- The call duration in seconds. 
	-- For successful calls this is the chargeable duration.
	-- For call attempts this is the call holding time.
	-- 
	
ManagementExtensions	::= SET SIZE (1) OF ManagementExtension

TimeStamp					::= OCTET STRING (SIZE(9))
	--
	-- The contents of this field are a compact form of the UTCTime format
	-- containing local time plus an offset to universal time. Binary coded
	-- decimal encoding is employed for the digits to reduce the storage and
	-- transmission overhead
	-- e.g. YYMMDDhhmmssShhmm
	-- where
	-- YY 	= 	Year 00 to 99		BCD encoded
	-- MM 	= 	Month 01 to 12 		BCD encoded
	-- DD	=	Day 01 to 31		BCD encoded
	-- hh	=	hour 00 to 23		BCD encoded
	-- mm	=	minute 00 to 59		BCD encoded
	-- ss	=	second 00 to 59		BCD encoded
	-- S	=	Sign 0 = "+", "-"	ASCII encoded
	-- hh	=	hour 00 to 23		BCD encoded
	-- mm	=	minute 00 to 59		BCD encoded
	--
	
MSISDN	::= ISDN-AddressString 
	-- 
	-- See TS GSM 03.03
	--
	
LocationAreaCode		::= OCTET STRING (SIZE(2))
	--
	-- See TS GSM 04.08
	--
	
MessageReference		::= OCTET STRING (SIZE(9))

RecordingEntity 		::= AddressString

SMSResult			::= Diagnostics

IMSI ::= TBCD-STRING (SIZE (3..8))
	-- digits of MCC, MNC, MSIN are concatenated in this order.

IMEI ::= TBCD-STRING (SIZE (8))
	--	Refers to International Mobile Station Equipment Identity
	--	and Software Version Number (SVN) defined in TS GSM 03.03.
	--	If the SVN is not present the last octet shall contain the
	--	digit 0 and a filler.
	--	If present the SVN shall be included in the last octet.

AddressString ::= OCTET STRING (SIZE (1..maxAddressLength))
	-- This type is used to represent a number for addressing
	-- purposes. It is composed of
	--	a)	one octet for nature of address, and numbering plan
	--		indicator.
	--	b)	digits of an address encoded as TBCD-String.

	-- 	a)	The first octet includes a one bit extension indicator, a
	--		3 bits nature of address indicator and a 4 bits numbering
	--		plan indicator, encoded as follows:

	-- bit 8: 1  (no extension)

	-- bits 765: nature of address indicator
	--	000  unknown
	--	001  international number
	--	010  national significant number
	--	011  network specific number
	--	100  subscriber number
	--	101  reserved
	--	110  abbreviated number
	--	111  reserved for extension

	-- bits 4321: numbering plan indicator
	--	0000  unknown
	--	0001  ISDN/Telephony Numbering Plan (Rec CCITT E.164)
	--	0010  spare
	--	0011  data numbering plan (CCITT Rec X.121)
	--	0100  telex numbering plan (CCITT Rec F.69)
	--	0101  spare
	--	0110  land mobile numbering plan (CCITT Rec E.212)
	--	0111  spare
	--	1000  national numbering plan
	--	1001  private numbering plan
	--	1111  reserved for extension

	--	all other values are reserved.

	-- b)	The following octets representing digits of an address
	--		encoded as a TBCD-STRING.

ISDN-AddressString ::= AddressString (SIZE (1..maxISDN-AddressLength))
	-- This type is used to represent ISDN numbers.

TBCD-STRING ::= OCTET STRING
	-- This type (Telephony Binary Coded Decimal String) is used to
	-- represent several digits from 0 through 9, *, #, a, b, c, two
	-- digits per octet, each digit encoded 0000 to 1001 (0 to 9),
	-- 1010 (*), 1011 (#), 1100 (a), 1101 (b) or 1110 (c); 1111 used
	-- as filler when there is an odd number of digits.

	-- bits 8765 of octet n encoding digit 2n
	-- bits 4321 of octet n encoding digit 2(n-1) +1

maxAddressLength  INTEGER ::= 20

maxISDN-AddressLength  INTEGER ::= 10

ManagementExtension ::= SEQUENCE {
				identifier		OBJECT IDENTIFIER,
				significance		[1] BOOLEAN DEFAULT FALSE,
				information		[2] ANY DEFINED BY identifier }

ConsolidationResult::= ENUMERATED
{
        normal                    	(0),
        notNormal                 	(1),
        forInterSGSNConsolidation 	(2),
        reachLimit			(3),
        onlyOneCDRGenerated		(4)
}

RecordNumber::= INTEGER
--
-- Should start from 1
--
RecordNumberList::= SEQUENCE OF RecordNumber
RECORDSequenceNumber ::= SEQUENCE
{
	gsnAddress		[0] GSNAddress,
	recordNumberList	[1] RecordNumberList
}


END
